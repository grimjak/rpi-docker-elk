-- ZyXEL Communications Corporation
-- Private Enterprise MIB definition 
  
-- This file describes the ZyXEL Communications Corporation Enterprise MIB.
-- It contains ZyXEL products OIDs, and common managed objects.

-- $Log: ZYXEL-SYSTEM-MGMT-MIB.mib $ 
-- Revision 1.11  2014/07/10 10:17:31  Alan 
-- add feature reload_stacking_default 
-- Revision 1.10  2014/06/16 10:40:11  Alan 
-- add zyxelSysMgmtReloadFactoryDefault 
-- Revision 1.9  2013/12/06 07:09:05  ccho 
-- remove uncessary imports 
-- Revision 1.8  2013/11/20 06:55:21  ccho 
-- renaming identifier name for SMI.V2 
-- Revision 1.7  2013/11/06 05:42:43  ccho 
-- fix mib style 
-- Revision 1.6  2013/08/01 06:53:47  Aga 
-- bug fix: for clear silverCreek faild message 
-- Revision 1.5  2013/06/26 07:03:41  Aga 
-- merge
--      Revision 1.5  2013/05/07 09:35:56  Aga  
--      bug fix: modify some oid for snmp privilege access control  
-- Revision 1.4  2012/09/19 08:16:45  Kevin 
-- if it's leaf node, revise the vender name from zyxel to zy 
-- Revision 1.3  2012/08/22 09:49:46  Kevin 
-- clean warning for SNMPc 
-- Revision 1.2  2012/07/05 06:24:55  Kevin 
-- 1. upgrade from SNMP to SNMPv2  
-- 2. clean warning 
-- Revision 1.1  2012/05/30 07:50:50  Kevin 
-- Initial revision 

ZYXEL-SYSTEM-MGMT-MIB DEFINITIONS ::= BEGIN

    IMPORTS
	OBJECT-TYPE
		FROM SNMPv2-SMI			-- RFC2578	
		
	MODULE-IDENTITY
		FROM SNMPv2-SMI

	InetAddressType, InetAddress
		FROM INET-ADDRESS-MIB		-- RFC2851				

	DisplayString                                          
	FROM SNMPv2-TC                             
	
	IpAddress
        FROM SNMPv2-SMI
  
	NOTIFICATION-TYPE
        FROM SNMPv2-SMI

	esMgmt			
		FROM ZYXEL-ES-SMI;

	zyxelManagement MODULE-IDENTITY
		LAST-UPDATED	"201207010000Z"    
		ORGANIZATION "Enterprise Solution ZyXEL"     
		CONTACT-INFO
			""	   
		DESCRIPTION
			"The subtree for management"
		::= { esMgmt 49 }
	
	zyxelSysMgmt     			OBJECT IDENTIFIER ::= { zyxelManagement 1 }
	zyxelSysMgmtNotifications OBJECT IDENTIFIER ::= { zyxelManagement 2 }
	
-- *******************************************************************
-- *
-- * zyxelSysMgmt
-- *
-- *******************************************************************
		
        
-- zyxelSysMgmtFirmwareUpgradeSetup                                                   
        zyxelSysMgmtFirmwareUpgradeSetup OBJECT IDENTIFIER ::= { zyxelSysMgmt 15 }                      

	zySysMgmtFirmwareUpgradeInetAddressType OBJECT-TYPE
        SYNTAX  INTEGER {         
        		unknown(0),
         		ipv4(1),
         		ipv6(2)           		
        }	
	
	MAX-ACCESS  read-write
	STATUS  current
	DESCRIPTION
		"A value that represents a type of Internet address."
	::= { zyxelSysMgmtFirmwareUpgradeSetup 1 }                        

	zySysMgmtFirmwareUpgradeInetAddress OBJECT-TYPE
	SYNTAX  DisplayString
	MAX-ACCESS  read-write
	STATUS  current
	DESCRIPTION
		"An InetAddress value is always interpreted within the context of an InetAddressType value."
	::= { zyxelSysMgmtFirmwareUpgradeSetup 2 } 

        zySysMgmtFirmwareUpgradeServerType OBJECT-TYPE
        SYNTAX  INTEGER {         
        		none(0),
         		Tftp(1)           		
        }
        MAX-ACCESS  read-write
        STATUS  current        
	DESCRIPTION
             "Type of firmware storage service."
        ::= { zyxelSysMgmtFirmwareUpgradeSetup 3 }    

        zySysMgmtFirmwareUpgradeRemoteFileName OBJECT-TYPE
        SYNTAX  DisplayString
        MAX-ACCESS  read-write
        STATUS  current
        DESCRIPTION
            "The file name that you want to upgrade from storage server."
        ::= { zyxelSysMgmtFirmwareUpgradeSetup 4 }     
        
        zySysMgmtFirmwareUpgradeFirmwareIndex OBJECT-TYPE
        SYNTAX  INTEGER {
        	    Firmware1(1),
        	    Firmware2(2)
        }
        MAX-ACCESS  read-write
        STATUS  current
        DESCRIPTION
            "Index of system firmware which you want to upgrade."
        ::= { zyxelSysMgmtFirmwareUpgradeSetup 5 }               
                               
        zySysMgmtFirmwareUpgradeAction OBJECT-TYPE
        SYNTAX  INTEGER {         
        		none(0),
         		upgrade(1)        		
        }
        MAX-ACCESS  read-write
        STATUS  current        
	DESCRIPTION
		" Action of firmware upgrade. 1: Upgrade firmware from storage server."
        ::= { zyxelSysMgmtFirmwareUpgradeSetup 6 }    
        
	zySysMgmtFirmwareUpgradeStatus OBJECT-TYPE
        SYNTAX  INTEGER {
        		none(0),
        		success(1),
        		fail(2),
        		underAction(3)
        }
        MAX-ACCESS  read-only
        STATUS  current
        DESCRIPTION
                      "Status of firmware upgrade."
        ::= { zyxelSysMgmtFirmwareUpgradeSetup 7 }     	

END
